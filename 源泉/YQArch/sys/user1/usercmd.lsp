;;;=========================================================================
;;;         源 泉 设 计    用户自编LSP程序例子
;;;-------------------------------------------------------------------------
;;; 文件夹 sys\用户文件夹\
;;;
;;;     “用户文件夹”为自建文件夹。将自编或收集到的“.lsp/.vlx/.arx”程序
;;; 文件放入此文件夹下，再设定此“用户文件夹”为当前用户(用命令yq_setuser)，
;;; 则“源泉设计”在启动的时候会自动加载这些程序。
;;;=========================================================================
;;; 注：1. 此文件是用户自编LSP程序例子；
;;;     2. 代码行中分号";"后面是注释，行首加分号则暂时取消该行。



;;;========================
;;; 一些简单自定义命令例子
;;;========================

(defun c:1`()
  (setvar "TILEMODE" (if (= (getvar "TILEMODE") 0) 1 0))
)

(defun c:``()
  (command(if(yq_ismodelspace)"pspace""mspace"))
)

;;; [用名称填充] 后5个参数: 填充名，比例，角度，是否保留外框，是否自动旋转
;(defun c:hnt() (yq_hatchrect "钢筋混凝土" 10 0 nil nil))      ; 钢筋混凝土
;(defun c:ck()  (yq_hatchrect "CORK" 1.5 0 t t))               ; 木夹板截面
;(defun c:sz()  (yq_hatchrect "CROSS" 10 45 nil nil))          ; 小十字


;;----- 新的语句可放在这里 -----







(princ)  ; 为最后一行
